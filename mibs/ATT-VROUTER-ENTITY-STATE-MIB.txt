-- *********************************************************************
-- ATT-VROUTER-ENTITY-STATE-MIB
--
-- Copyright (c) 2018-2019 by AT&T Intellectual Property.
-- All rights reserved.
--
-- Redistribution and use in source and binary forms, with or without
-- modification, are permitted provided that the following conditions
-- are met:
--
-- 1. Redistributions of source code must retain the above copyright
-- notice, this list of conditions and the following disclaimer.
-- 2. Redistributions in binary form must reproduce the above
-- copyright notice, this list of conditions and the following
-- disclaimer in the documentation and/or other materials provided
-- with the distribution.
-- 3. Neither the name of the copyright holder nor the names of its
-- contributors may be used to endorse or promote products derived
-- from this software without specific prior written permission.
--
-- THIS SOFTWARE IS PROVIDED BY THE COPYRIGHT HOLDERS AND CONTRIBUTORS
-- 'AS IS' AND ANY EXPRESS OR IMPLIED WARRANTIES, INCLUDING, BUT NOT
-- LIMITED TO, THE IMPLIED WARRANTIES OF MERCHANTABILITY AND FITNESS
-- FOR A PARTICULAR PURPOSE ARE DISCLAIMED. IN NO EVENT SHALL THE
-- COPYRIGHT HOLDER OR CONTRIBUTORS BE LIABLE FOR ANY DIRECT, INDIRECT,
-- INCIDENTAL, SPECIAL, EXEMPLARY, OR CONSEQUENTIAL DAMAGES (INCLUDING,
-- BUT NOT LIMITED TO, PROCUREMENT OF SUBSTITUTE GOODS OR SERVICES;
-- LOSS OF USE, DATA, OR PROFITS; OR BUSINESS INTERRUPTION) HOWEVER
-- CAUSED AND ON ANY THEORY OF LIABILITY, WHETHER IN CONTRACT, STRICT
-- LIABILITY, OR TORT (INCLUDING NEGLIGENCE OR OTHERWISE) ARISING IN
-- ANY WAY OUT OF THE USE OF THIS SOFTWARE, EVEN IF ADVISED OF THE
-- POSSIBILITY OF SUCH DAMAGE.
--
-- SPDX-License-Identifier: BSD-3-Clause
--
-- *********************************************************************
ATT-VROUTER-ENTITY-STATE-MIB DEFINITIONS ::= BEGIN

IMPORTS
        MODULE-IDENTITY, NOTIFICATION-TYPE,
        enterprises
                FROM SNMPv2-SMI
        entStateAdmin, entStateOper,
        entStateLastChanged
                FROM ENTITY-STATE-MIB
        entPhysicalClass, entPhysicalContainedIn,
        entPhysicalVendorType, entPhysicalName,
        entPhysicalModelName
                FROM ENTITY-MIB;

attVRouterEntityStateMIB MODULE-IDENTITY
     LAST-UPDATED "201806180000Z"
     ORGANIZATION "AT&T Inc."
     CONTACT-INFO
     "Postal: 208 S. Akard Street
              Dallas, TX 25202
      Web:    www.att.com
     "
     DESCRIPTION
            "This module defines Entity State MIB extensions for FRU
             state change notifications.

             Copyright (C) 2018, AT&T Intellectual Property."

     REVISION        "201806180000Z"
     DESCRIPTION
            "Initial version"
     ::= { attVrouter 3 }

attEnterprise   OBJECT IDENTIFIER ::= { enterprises 74 }
attProducts     OBJECT IDENTIFIER ::= { attEnterprise 1 }
attVrouter      OBJECT IDENTIFIER ::= { attProducts 32 }

entStateExtNotifications        OBJECT IDENTIFIER
     ::= { attVRouterEntityStateMIB 0 }

--
-- entStateExtNotifications
--

entStatusChange NOTIFICATION-TYPE
    OBJECTS { entPhysicalClass,
              entStateOper,
              entStateAdmin,
              entStateLastChanged
            }
    STATUS      current
    DESCRIPTION
            "A notification indicates that the status of 
            entPhysicalIndex has changed."
    ::= { entStateExtNotifications 1 }

entFRUInserted NOTIFICATION-TYPE
    OBJECTS { entPhysicalClass,
              entPhysicalContainedIn
            }
    STATUS      current
    DESCRIPTION
            "A notification indicates that entPhysicalIndex
            FRU has been inserted."
    ::= { entStateExtNotifications 2 }

entFRURemoved NOTIFICATION-TYPE
    OBJECTS { entPhysicalClass,
              entPhysicalContainedIn
            }
    STATUS      current
    DESCRIPTION
            "A notification indicates that entPhysicalIndex
            FRU has been removed."
    ::= { entStateExtNotifications 3 }

entUnrecognizedFRU NOTIFICATION-TYPE
    OBJECTS { entPhysicalClass,
              entPhysicalVendorType,
              entPhysicalName,
              entPhysicalModelName,
              entStateOper,
              entStateAdmin,
              entStateLastChanged
            }
    STATUS      current
    DESCRIPTION
            "A notification indicates that entPhysicalIndex
             FRU that is inserted is unrecognized."
    ::= { entStateExtNotifications 4 }

END
